(setq *slope* "2x10")
(setq *msename* "MEIOSE")
(defun c:psv()
  	(command "undo" "begin")
  	(setq sel1 (ssget))
  	(princ "setup")
  	(progn
		(setq i 2)
    		(setq tmp (getstring (strcat "\nRelacao < " *slope* ">: ")))
	  	(if (= tmp nil)
		 (setq tmp *slope*)
		)
	  	(if (= tmp "")
		 (setq tmp *slope*)
		)
	  	(setq lname (getstring (strcat "\nNome Layer < " *msename* ">: ")))
	  	(if (= lname nil)
		 (setq lname *msename*)
		)
	  	(if (= lname "")
		 (setq lname *msename*)
		)
	  	(setq *slope* tmp)
	  	(setq *msename* lname)
	  	(princ (strcat "\nRelacao" tmp))
	  	(setq tmp2 tmp)
	  	(setq tmprmae (substr tmp 1 1))
	  	(setq tmpvao (substr tmp2 3))
	  	(princ (strcat "\nRMAE:" tmprmae "RVAO:" tmpvao))
	  	(setq resto (+ (atoi tmpvao) (atoi tmprmae)))
	  	(while (setq ent (ssname sel1 i))
		(if (= (rem i resto) (atoi tmprmae))
		(progn
		  	;(setq ent2 (ssname sel1 (+ tmprmae (+ 1 i))
		  	;(command "_.chprop" ent "" "_layer" lname "_c" "ByLayer" "")
		  	;(setq h1 (+ i 1))
		  	(setq ent1 (ssname sel1 (+ i 1)))
		  	(command "_.chprop" ent1 "" "_layer" lname "_c" "ByLayer" "")
			;(princ (- (atoi tmprmae) i))
			(setq ent2 (ssname sel1 (- i (atoi tmprmae))))
		  	(command "_.chprop" ent2 "" "_layer" lname "_c" "ByLayer" "")
			(princ i)
		  )
		 )
		(setq i (1+ i))
	  	)
	)
  	(command "undo" "end")
)
